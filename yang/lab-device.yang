module lab-device {
  yang-version 1.1;
  namespace "http://example.com/ns/lab-device";
  prefix ld;

  import ietf-inet-types { prefix inet; }

  organization "Lab";
  description
    "A minimal network device model to practice NETCONF/YANG.";

  container interfaces {
    description "Interface configuration";

    list interface {
      key "name";
      description "One interface";

      leaf name {
        type string;
        description "Interface name (e.g., GigabitEthernet0/0)";
      }

      leaf enabled {
        type boolean;
        default "true";
      }

      leaf description {
        type string;
      }

      leaf mtu {
        type uint16 {
          range "128..9216";
        }
        default "1500";
      }

      container ipv4 {
        list address {
          key "ip";
          leaf ip {
            type inet:ipv4-address;
          }
          leaf prefix-length {
            type uint8 { range "0..32"; }
          }
        }
      }
    }
  }
}
