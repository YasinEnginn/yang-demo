module lab-net-device-deviations-srlinux {
  yang-version 1.1;
  namespace "http://example.com/ns/lab-net-device-deviations/srlinux";
  prefix lndd;

  import lab-net-device {
    prefix lnd;
    revision-date 2026-02-11;
  }

  organization "Lab";
  contact
    "Web: <https://github.com/YasinEnginn/YANG>";

  description
    "Deviations for a specific platform profile (example: SR Linux lab image).";

  revision 2026-02-11 {
    description "Update base module revision reference.";
    reference "0.2.0";
  }
  revision 2026-02-10 {
    description "Initial deviation declarations.";
    reference "0.1.0";
  }

  deviation "/lnd:bgp/lnd:neighbor/lnd:vrf" {
    deviate not-supported;
  }

  deviation "/lnd:interfaces/lnd:interface/lnd:bounce" {
    deviate not-supported;
  }

  deviation "/lnd:interfaces/lnd:interface/lnd:switchport" {
    deviate not-supported;
  }
}
